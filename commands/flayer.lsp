(defun make-spaces (n)
  (if (> n 0)
    (strcat " " (make-spaces (1- n)))
    ""
  )
)

(defun c::flayer ( / input-layer layer-name layer-list counter key-list key-char page layers-per-page layer-names total-pages all-layer-names layer-map user-input max-layer-name-length start-index end-index current-layers i)
  (setq input-layer (getstring "\nEnter layer name or partial name to filter: "))
  (setq input-layer (strcase input-layer))  
  (textscr)  
  (setq layer-list (vla-get-layers (vla-get-activedocument (vlax-get-acad-object))))  
  (setq counter 0)
  (setq layers-per-page 15)
  (setq key-list '("A" "S" "D" "F" "J" "K" "L" "G" "H" "W" "E" "R" "U" "I" "O" "P"))  
  (setq all-layer-names '())
  (setq layer-map '())
  (setq max-layer-name-length 0)

  (vlax-for layer layer-list
    (setq layer-name (strcase (vla-get-name layer)))  
    (if (wcmatch layer-name (strcat "*" input-layer "*"))
      (progn
        (setq all-layer-names (append all-layer-names (list layer-name)))
        (setq max-layer-name-length (max max-layer-name-length (strlen layer-name)))
      )
    )
  )

  (setq total-pages (/ (+ (length all-layer-names) (1- layers-per-page)) layers-per-page))
  (setq page 1)

  (defun show-page ()
    (setq current-layer (strcase (getvar "CLAYER")))  
    (princ "\n")  
    (setq start-index (* (1- page) layers-per-page))
    (setq end-index (min (length all-layer-names) (* page layers-per-page)))
    (setq current-layers '())
    (setq i start-index)
    (while (< i end-index)
      (setq current-layers (append current-layers (list (nth i all-layer-names))))
      (setq i (1+ i))
    )
    (setq layer-map '())  
    (if (> total-pages 1)
      (princ (strcat "\nPage " (itoa page) "/" (itoa total-pages) ":\n\n"))
      (princ "\n")
    )
    (princ "[A] All\n\n")  
    (setq counter 0)
    (while (< counter (length current-layers))
      (setq key-char (nth (1+ counter) key-list))  
      (setq layer (vla-item layer-list (nth counter current-layers)))  
      (setq status "")
      (setq status (strcat "(" 
                           (if (= (vla-get-layeron layer) :vlax-true) "On" "Off") ", "  
                           (if (= (vla-get-lock layer) :vlax-true) "Locked" "Unlocked") ", "  
                           (if (= (vla-get-freeze layer) :vlax-true) "Frozen" "Unfrozen") ", "  
                           (if (= (vla-get-plottable layer) :vlax-true) "Plottable" "Not Plottable")  
                           ")"))
      (setq layer-name-display (nth counter current-layers))
      (if (equal layer-name-display current-layer)
        (setq layer-name-display (strcat layer-name-display "*")))
      (setq layer-map (cons (cons key-char (nth counter current-layers)) layer-map))  
      (princ (strcat "[" key-char "] " layer-name-display (make-spaces (- (+ max-layer-name-length 3) (strlen layer-name-display))) status "\n"))  
      (setq counter (1+ counter))  
    )
    (if (> total-pages 1)
      (princ (strcat "\nEnd of Page " (itoa page) "/" (itoa total-pages) "\n"))
    )
    (princ "\nActions:\n")
    (princ "On/Off (O/X)          Freeze/Unfreeze (F/T)\n")
    (princ "Lock/Unlock (L/R)     Plottable/Not Plottable (P/Q)\n")
  )

  (show-page)

  (while t
    (setq user-input (strcase (getstring "\nEnter tag and action (e.g., SO to turn first layer On, AF for All Freeze): ")))  
    (cond
      ((equal user-input "N")
       (setq page (if (= page total-pages) 1 (1+ page)))
       (show-page)
      )
      ((= (substr user-input 1 1) "A")
       (cond
         ((= (substr user-input 2 1) "F")  
          (foreach layer-name all-layer-names
            (if (not (equal (strcase layer-name) current-layer))
              (progn
                (setq layer (vla-item layer-list layer-name))
                (vla-put-freeze layer :vlax-true)
              )
            )
          )
          (princ "\nAll applicable layers are now frozen.\n")
         )
         ((= (substr user-input 2 1) "T")  
          (foreach layer-name all-layer-names
            (setq layer (vla-item layer-list layer-name))
            (vla-put-freeze layer :vlax-false)
          )
          (princ "\nAll filtered layers are now unfrozen.\n")
         )
         ((= (substr user-input 2 1) "L")  
          (foreach layer-name all-layer-names
            (setq layer (vla-item layer-list layer-name))
            (vla-put-lock layer :vlax-true)
          )
          (princ "\nAll filtered layers are now locked.\n")
         )
         ((= (substr user-input 2 1) "R")  
          (foreach layer-name all-layer-names
            (setq layer (vla-item layer-list layer-name))
            (vla-put-lock layer :vlax-false)
          )
          (princ "\nAll filtered layers are now unlocked.\n")
         )
         ((= (substr user-input 2 1) "O")  
          (foreach layer-name all-layer-names
            (setq layer (vla-item layer-list layer-name))
            (vla-put-layeron layer :vlax-true)
          )
          (princ "\nAll filtered layers are now on.\n")
         )
         ((= (substr user-input 2 1) "X")  
          (foreach layer-name all-layer-names
            (setq layer (vla-item layer-list layer-name))
            (vla-put-layeron layer :vlax-false)
          )
          (princ "\nAll filtered layers are now off.\n")
         )
         ((= (substr user-input 2 1) "P")  
          (foreach layer-name all-layer-names
            (setq layer (vla-item layer-list layer-name))
            (vla-put-plottable layer :vlax-true)
          )
          (princ "\nAll filtered layers are now plottable.\n")
         )
         ((= (substr user-input 2 1) "Q")  
          (foreach layer-name all-layer-names
            (setq layer (vla-item layer-list layer-name))
            (vla-put-plottable layer :vlax-false)
          )
          (princ "\nAll filtered layers are now not plottable.\n")
         )
       )
       (textscr)  
       (show-page)  
      )
      ((assoc (substr user-input 1 1) layer-map)
       (setq layer-name (cdr (assoc (substr user-input 1 1) layer-map)))
       (cond
         ((= (substr user-input 2 1) "F")  
          (if (not (equal (strcase layer-name) current-layer))
            (vla-put-freeze (vla-item layer-list layer-name) :vlax-true)
            (princ (strcat "\nLayer " layer-name " cannot be frozen because it is the current layer.\n"))
          )
         )
         ((= (substr user-input 2 1) "T")  
          (vla-put-freeze (vla-item layer-list layer-name) :vlax-false)
          (princ (strcat "\nLayer " layer-name " is now unfrozen.\n"))
         )
         ((= (substr user-input 2 1) "L")  
          (vla-put-lock (vla-item layer-list layer-name) :vlax-true)
          (princ (strcat "\nLayer " layer-name " is now locked.\n"))
         )
         ((= (substr user-input 2 1) "R")  
          (vla-put-lock (vla-item layer-list layer-name) :vlax-false)
          (princ (strcat "\nLayer " layer-name " is now unlocked.\n"))
         )
         ((= (substr user-input 2 1) "O")  
          (vla-put-layeron (vla-item layer-list layer-name) :vlax-true)
          (princ (strcat "\nLayer " layer-name " is now on.\n"))
         )
         ((= (substr user-input 2 1) "X")  
          (vla-put-layeron (vla-item layer-list layer-name) :vlax-false)
          (princ (strcat "\nLayer " layer-name " is now off.\n"))
         )
         ((= (substr user-input 2 1) "P")  
          (vla-put-plottable (vla-item layer-list layer-name) :vlax-true)
          (princ (strcat "\nLayer " layer-name " is now plottable.\n"))
         )
         ((= (substr user-input 2 1) "Q")  
          (vla-put-plottable (vla-item layer-list layer-name) :vlax-false)
          (princ (strcat "\nLayer " layer-name " is now not plottable.\n"))
         )
         (t  
          (setq doc (vla-get-activedocument (vlax-get-acad-object)))
          (vla-put-activelayer doc (vla-item layer-list layer-name))
          (princ (strcat "\nLayer " layer-name " is now the current layer.\n"))
         )
       )
       (textscr)  
       (show-page)  
      )
      (t
       (princ "\nInvalid input. Please try again.\n")
       (textscr)  
      )
    )
  )
)
